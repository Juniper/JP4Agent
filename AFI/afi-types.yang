//
//
// AFI : Types
//
// Created by Sandesh Kumar Sodhi, January 2018
// Copyright (c) [2018] Juniper Networks, Inc. All rights reserved.
//

module afi-types {

    yang-version "1";

    namespace "http://yang.juniper.net/yang/1.1/jc/afi-types/junos/17.3";
    prefix "afi-types";

    organization
        "Juniper Networks, Inc.";

    contact
        "Sandesh Kumar Sodhi
        sksodhi@juniper.net";

    description
      "This module provides data model for Juniper's Advanced Forwarding Interface";

    revision 2017-12-02 {
        description "Initial revision.";
    }
 
    typedef afi-type-index {
        description "Aft type index";
        type uint32;
    }

    typedef afi-protocol-index {
        description "Protocol index";
        type uint32;
    }

    typedef afi-proto-family {
        description "AFI protocol family";
        type enumeration {
            enum inet {
             description
              "Inet/IPv4";
            }
            enum inet6 {
             description
              "Inet6/IPv6";
            }
            enum mpls {
             description
              "MPLS";
            }
        }
    }

    typedef afi-inet-family {
        description "AFI IPv4 protocol family";
        type enumeration {
            enum tcp {
             description
              "TCP";
            }
            enum udp {
             description
              "UDP";
            }
            enum igmp {
             description
              "IGMP";
            }
            enum icmp {
             description
              "ICMP";
            }
        }
    }

    typedef afi-field {
        description "AFI field";
        type enumeration {
            enum ingress-port {
             description
              "Ingress port";
            }

            enum egress-port {
             description
              "Egress port";
            }

            enum packet-ether-daddr {
             description
              "Packet Ethernet destination MAC address";
            }

            enum packet-ether-saddr {
             description
              "Packet Ethernet source MAC address";
            }

            enum packet-ether-type {
             description
              "Packet Ethernet header ether_type";
            }

            enum packet-ether-vlan1-tag-vid {
             description
              "Packet Ethernet vlan1 tag vlan id";
            }

            enum packet-arp-target-proto-addr {
             description
              "ARP packet target proto address";
            }

            enum packet-ether-vlan1-tag-pcp {
             description
              "Packet Ethernet vlan1 tag pcp";
            }

            enum packet-ip4-daddr {
             description
              "Packet IPv4 destination address";
            }

            enum packet-ip4-saddr {
             description
              "Packet IPv4 source address";
            }

            enum packet-ip4-protocol {
             description
              "Packet IPv4 protocol";
            }

            enum packet-ip4-diffserv {
             description
              "Packet IPv4 diffserv";
            }

            enum packet-ip4-ttl {
             description
              "Packet IPv4 ttl";
            }

            enum packet-ip6-daddr {
             description
              "Packet IPv6 destination address";
            }

            enum packet-ip6-saddr {
             description
              "Packet IPv6 source address";
            }

            enum packet-ip6-traffic-class {
             description
              "Packet IPv6 traffic-class";
            }

            enum packet-ip6-flow-label {
             description
              "Packet IPv6 flow-label";
            }

            enum packet-ip6-next-header {
             description
              "Packet IPv6 next header";
            }

            enum packet-ip6-hop-limit {
             description
              "Packet IPv6 hop limit";
            }

            enum packet-icmp-type {
             description
              "Packet ICMP type";
            }

            enum packet-l4-sport {
             description
              "Packet layer 4 source port";
            }

            enum packet-l4-dport {
             description
              "Packet layer 4 destination port";
            }

            enum packet-l3-class-id {
             description
              "Packet layer 3 class-id";
            }

            enum packet-encap-type {
             description
              "Packet encapuslation type";
            }

            enum packet-outer-ipv4-src-addr {
             description
              "Packet Outer IPv4 source address";
            }

            enum packet-outer-ipv4-dst-addr {
             description
              "Packet Outer IPv4 destination address";
            }

            enum packet-outer-ipv6-src-addr {
             description
              "Packet Outer IPv6 source address";
            }

            enum packet-outer-ipv6-dst-addr {
             description
              "Packet Outer IPv6 destination address";
            }

            enum packet-gre-flags {
             description
              "Packet GRE flags";
            }
        }
    }

    typedef afi-class-id {
        description "Packet classification identifier";
        // platform-specific type, range
        type int16 {
            range "0..4095";
        }
    }

    typedef afi-port {
        description "AFI Port";
        // platform-specific type, range
        type uint8;
    }

    typedef afi-trunk-group-id {
        description "AFI Trunk Group id";
        // platform-specific type, range
        type uint16;
    }

    typedef afi-vrf-id {
        description "VRF ID";
        // platform-specific type, range
        type int16 {
            range "0..4095";
        }
    }

    typedef afi-tree-type {
        description "AFI tree type";
        type enumeration {
            enum override {
                description "Override table";
            }

            enum vrf {
                description "VRF table";
            }

            enum fallback {
                description "Fallback table";
            }
        }
    }
}

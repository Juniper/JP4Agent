//
// Copyright (c) 2017 Juniper Networks, Inc.
// All rights reserved. 
//

module afi-common {

    yang-version "1";

    namespace "http://yang.juniper.net/yang/1.1/jc/afi-cmn/junos/17.3";
    prefix "afi-cmn";

    organization
        "Juniper Networks, Inc.";

    contact
        "Sandesh Kumar Sodhi
        sksodhi@juniper.net";

    description
      "This module provides data model for Juniper's Advanced Forwarding Interface";

    revision 2017-12-02 {
        description "Initial revision.";
    }   
 
}

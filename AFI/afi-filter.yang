//
// Juniper AFI : AFI Filter
//
// Created by Sandesh Kumar Sodhi, January 2018
// Copyright (c) [2018] Juniper Networks, Inc. All rights reserved.
//
//

module afi-filter {

    yang-version "1";

    namespace "http://yang.juniper.net/yang/1.1/jc/afi-filter/junos/17.3";
    prefix "afi-filter";

    import afi-types  { prefix "afi-types"; }
    import afi-common { prefix "afi-cmn"; }

    organization
        "Juniper Networks, Inc.";

    contact
        "Sandesh Kumar Sodhi
        sksodhi@juniper.net";

    description
      "This module provides data model for AFI Filter";

    revision 2017-12-02 {
        description "Initial revision.";
    }

    container afi-filter {
        description "TBD";

    }
}

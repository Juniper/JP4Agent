//
// Juniper AFI : Encap
//
// Created by Sandesh Kumar Sodhi, January 2018
// Copyright (c) [2018] Juniper Networks, Inc. All rights reserved.
//
//

module afi-encap {

    yang-version "1";

    namespace "http://yang.juniper.net/yang/1.1/jc/afi-encap/junos/17.3";
    prefix "afi-encap";

    import afi-types  { prefix "afi-types"; }

    organization
        "Juniper Networks, Inc.";

    contact
        "Sandesh Kumar Sodhi
        sksodhi@juniper.net";

    description
      "Encap";

    revision 2017-12-02 {
        description "Initial revision.";
    }

    container afi-encap {
        description "AFI Encap";

        leaf name {
            description "Name";
            type string;
        }

        leaf encap-name {
            type string;
            description "Encapsulation name";
        }

        leaf-list key-fields {
            type afi-types:afi-field;
            description "List of fields";
        }
    }
}

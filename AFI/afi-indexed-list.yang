//
// Juniper AFI : Indexed list
//
// Created by Sandesh Kumar Sodhi, January 2018
// Copyright (c) [2018] Juniper Networks, Inc. All rights reserved.
//
//

module afi-indexed-list {

    yang-version "1";

    namespace "http://yang.juniper.net/yang/1.1/jc/afi-indexed-list/junos/17.3";
    prefix "afi-indexed-list";

    import afi-types  { prefix "afi-types"; }
    import afi-common { prefix "afi-cmn"; }

    organization
        "Juniper Networks, Inc.";

    contact
        "Sandesh Kumar Sodhi
        sksodhi@juniper.net";

    description
      "AFI indexed list";

    revision 2017-12-02 {
        description "Initial revision.";
    }

    container afi-indexed-list {
        description "TBD";

    }
}

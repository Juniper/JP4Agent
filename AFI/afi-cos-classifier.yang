//
// Juniper AFI : COS Classifier
//
// Created by Sandesh Kumar Sodhi, January 2018
// Copyright (c) [2018] Juniper Networks, Inc. All rights reserved.
//
//

module afi-cos-classifier {

    yang-version "1";

    namespace "http://yang.juniper.net/yang/1.1/jc/afi-cos-classifier/junos/17.3";
    prefix "afi-cos-classifier";


    import afi-types  { prefix "afi-types"; }
    import afi-common { prefix "afi-cmn"; }

    organization
        "Juniper Networks, Inc.";

    contact
        "Sandesh Kumar Sodhi
        sksodhi@juniper.net";

    description
      "COS classifier";

    revision 2017-12-02 {
        description "Initial revision.";
    }

    container cos-classifier {
        description "Class of Service Classifier";

        leaf name {
            description "Name";
            type string;
        }   
    }
}

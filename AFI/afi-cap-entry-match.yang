//
// Juniper AFI : AFI Cap Entry Match Set
//
// Created by Sudheendra Gopinath, June 2018
// Copyright (c) [2018] Juniper Networks, Inc. All rights reserved.
//
//

module afi-cap-entry-match {

    yang-version "1";

    namespace "http://yang.juniper.net/yang/1.1/jc/afi-cap-entry-match/junos/17.3";
    prefix "afi-cap-entry-match";

    import afi-types  { prefix "afi-types"; }

    organization
        "Juniper Networks, Inc.";

    contact
        "Sudheendra Gopinath
         sgopinath@juniper.net";

    description
      "This module provides data model for AFI Content Aware Processor Entry Match Set";

    revision 2018-06-02 {
        description "Initial revision.";
    }

    container afi-cap-entry-match {
        description "AFI Content Aware Processor Match Fields";
    
        leaf pipeline-id {
            type uint8;
            description "Pipeline number";
        }
    
        leaf pipeline-id-mask {
            type uint8;
            description "Pipeline number mask";
        }
    
        leaf virtual-slice-group {
            type uint8;
            description "Virtual slice group";
        }
    
        leaf virtual-slice-group-mask {
            type uint8;
            description "Virtual slice group mask";
        }
    
        leaf vlan-outer-present {
            type boolean;
            description "Packet Outer Vlan Tag Status";
        }
    
        leaf vlan-outer-present-mask {
            type boolean;
            description "Packet Outer Vlan Tag Status mask";
        }
    
        leaf outer-vlan-id {
            type uint16 {
                range "1 .. 4095";
            }
            description "Outer Vlan Id";
        }
    
        leaf outer-vlan-id-mask {
            type uint16 {
                range "1 .. 4095";
            }
            description "Outer Vlan Id mask";
        }
    
        leaf outer-vlan-cfi {
            type boolean;
            description "Outer Vlan CFI";
        }
    
        leaf outer-vlan-cfi-mask {
            type boolean;
            description "Outer Vlan CFI mask";
        }
    
        leaf outer-vlan-dot1p {
            type uint8 {
                range "0 .. 7";
            }
            description "Outer Vlan Priority";
        }
    
        leaf outer-vlan-dot1p-mask {
            type uint8 {
                range "0 .. 7";
            }
            description "Outer Vlan Priority mask";
        }
    
        leaf vlan-inner-present {
            type boolean;
            description "Packet Outer Vlan Tag Status";
        }
    
        leaf vlan-inner-present-mask {
            type boolean;
            description "Packet Outer Vlan Tag Status mask";
        }
    
        leaf inner-vlan-id {
            type uint16 {
                range "1 .. 4095";
            }
            description "Inner Vlan Id";
        }
    
        leaf inner-vlan-id-mask {
            type uint16 {
                range "1 .. 4095";
            }
            description "Inner Vlan Id mask";
        }
    
        leaf inner-vlan-cfi {
            type boolean;
            description "Inner Vlan CFI";
        }
    
        leaf inner-vlan-cfi-mask {
            type boolean;
            description "Inner Vlan CFI mask";
        }
    
        leaf inner-vlan-dot1p {
            type uint8 {
                range "0 .. 7";
            }
            description "Inner Vlan Priority";
        }
    
        leaf inner-vlan-dot1p-mask {
            type uint8 {
                range "0 .. 7";
            }
            description "Inner Vlan Priority mask";
        }
    
        leaf inner-ip-proto {
            type uint8;
            description "Inner IP Protocol";
        }
    
        leaf inner-ip-proto-mask {
            type uint8;
            description "Inner IP Protocol mask";
        }
    
        leaf outer-ip-proto {
            type uint8;
            description "Outer IP Protocol";
        }
    
        leaf outer-ip-proto-mask {
            type uint8;
            description "Outer IP Protocol mask";
        }
    
        leaf tunnel-terminated {
            type boolean;
            description "Tunnel terminated traffic";
        }
    
        leaf tunnel-terminated-mask {
            type boolean;
            description "Tunnel terminated traffic mask";
        }
    
        leaf outer-tpid {
            type afi-types:afi-field;
            description "Outer TPID of the packet.";
        }
    
        leaf outer-tpid-mask {
            type afi-types:afi-field;
            description "Outer TPID of the packet mask.";
        }
    
        leaf source-trunk {
            type afi-types:afi-trunk-group-id;
            description "Source Trunk Group ID.";
        }
    
        leaf source-trunk-mask {
            type afi-types:afi-trunk-group-id;
            description "Source Trunk Group ID mask.";
        }
    
        leaf source-port {
            type afi-types:afi-port;
            description "Source Port.";
        }
    
        leaf source-port-mask {
            type afi-types:afi-port;
            description "Source Port mask.";
        }
    
        leaf destination-port {
            type afi-types:afi-port;
            description "Destination Port.";
        }
    
        leaf destination-port-mask {
            type afi-types:afi-port;
            description "Destination Port mask.";
        }
    
        leaf system-port-class {
            type afi-types:afi-class-id;
            description "Class Id from SOURCE_TRUNK_MAP.";
        }
    
        leaf system-port-class-mask {
            type afi-types:afi-class-id;
            description "Class Id from SOURCE_TRUNK_MAP mask.";
        }
    
        leaf l4-packet {
            type boolean;
            description "L4 Packet (has Valid L4 Source and Destination Port).";
        }
    
        leaf l4-packet-mask {
            type boolean;
            description "L4 Packet mask (has Valid L4 Source and Destination Port).";
        }
    
        leaf ipv4-ttl {
            type uint8;
            description "Packet TTL.";
        }
    
        leaf ipv4-ttl-mask {
            type uint8;
            description "Packet TTL mask.";
        }
    
        leaf tos {
            type uint8;
            description "Packet TOS.";
        }
    
        leaf tos-mask {
            type uint8;
            description "Packet TOS mask.";
        }
    
        leaf l4-destination-port {
            type uint16;
            description "L4 Header Destination Port.";
        }
    
        leaf l4-destination-port-mask {
            type uint16;
            description "L4 Header Destination Port mask.";
        }
    
        leaf l4-source-port {
            type uint16;
            description "L4 header Source Port.";
        }
    
        leaf l4-source-port-mask {
            type uint16;
            description "L4 header Source Port mask.";
        }
    
        leaf ip-protocol {
            type uint8;
            description "IP Protocol.";
        }
    
        leaf ip-protocol-mask {
            type uint8;
            description "IP Protocol mask.";
        }
    
        leaf destination-ipv4-address {
            type uint32;
            description "Destination IPv4 address.";
        }
    
        leaf destination-ipv4-address-mask {
            type uint32;
            description "Destination IPv4 address mask.";
        }
    
        leaf source-ipv4-address {
            type uint32;
            description "Source IPv4 address.";
        }
    
        leaf source-ipv4-address-mask {
            type uint32;
            description "Source IPv4 address mask.";
        }
    
        leaf ethertype {
            type uint16;
            description "Ethertype.";
        }
    
        leaf ethertype-mask {
            type uint16;
            description "Ethertype mask.";
        }
    
        leaf source-mac-address {
            type binary {
                length "6";
            }
            description "Source MAC address.";
        }
    
        leaf source-mac-address-mask {
            type binary {
                length "6";
            }
            description "Source MAC address mask.";
        }
    
        leaf destination-mac-address {
            type binary {
                length "6";
            }
            description "Destination MAC address.";
        }
    
        leaf destination-mac-address-mask {
            type binary {
                length "6";
            }
            description "Destination MAC address mask.";
        }
    
        leaf l3-interface-class {
            type uint16;
            description "L3 interface Class ID.";
        }

        leaf l3-interface-class-mask {
            type uint16;
            description "L3 interface Class ID mask.";
        }
    
        leaf virtual-routing-and-forwarding-id {
            type uint32;
            description "VRF ID.";
        }

        leaf virtual-routing-and-forwarding-id-mask {
            type uint32;
            description "VRF ID mask.";
        }

        leaf ingress-class-id {
            type uint8;
            description "Class ID assigned by ingress stage.";
        }

        leaf ingress-class-id-mask {
            type uint8;
            description "Class ID mask.";
        }

        leaf arp-target-ipv4-address {
            type uint32;
            description "Target IPv4 Address in ARP header.";
        }

        leaf arp-target-ipv4-address-mask {
            type uint32;
            description "ARP Target IPv4 Address mask.";
        }

        leaf icmp-type {
            type uint8;
            description "ICMP type.";
        }

        leaf icmp-type-mask {
            type uint8;
            description "ICMP type mask.";
        }
    }
}
